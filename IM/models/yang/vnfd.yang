/*
 *
 *   Copyright 2016-2017 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module vnfd
{
  namespace "urn:etsi:osm:yang:vnfd";
  prefix "vnfd";

  import vnfd-base {
    prefix "vnfd-base";
  }

  revision 2017-02-28 {
    description
      "Update model to support projects.";
  }

  revision 2015-09-10 {
    description
      "Initial revision. This YANG file defines
       the Virtual Network Function (VNF)";
    reference
      "Derived from earlier versions of base YANG files";
  }
  container vnfd-catalog {
    description
      "Virtual Network Function Descriptor (VNFD).";

    leaf schema-version {
      description "Schema version for the VNFD. If unspecified, it assumes v3.0";
      type string;
      default "v3.0";
    }

    list vnfd {
      key "id";

      uses vnfd-base:vnfd-descriptor;
    }
  }
}

// vim: sw=2
