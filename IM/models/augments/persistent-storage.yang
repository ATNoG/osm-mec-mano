/*
  Copyright ETSI

  Licensed under the Apache License, Version 2.0 (the "License");
  you may not use this file except in compliance with the License.
  You may obtain a copy of the License at

    http://www.apache.org/licenses/LICENSE-2.0

  Unless required by applicable law or agreed to in writing, software
  distributed under the License is distributed on an "AS IS" BASIS,
  WITHOUT WARRANTIES OR CONDITIONS OF ANY KIND, either express or
  implied.
  See the License for the specific language governing permissions and
  limitations under the License.
*/

module persistent-storage {
    yang-version 1.1;
    namespace "urn:etsi:osm:yang:augments:persistent-storage";
    prefix "persistent-storage";

    import etsi-nfv-descriptors {
        prefix descriptors;
    }

    import etsi-nfv-vnfd {
        prefix vnfd;
    }

    identity persistent-storage {
        base descriptors:storage-type;
        description
            "Persistent type of storage.";
    }

    augment "/vnfd:vnfd/vnfd:virtual-storage-desc" {
        when 'derived-from-or-self(vnfd:type-of-storage, "persistent-storage:persistent-storage")';
    }
}
