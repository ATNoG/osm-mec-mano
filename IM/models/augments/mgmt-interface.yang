/*
  Copyright 2020 Whitestack LLC

  Licensed under the Apache License, Version 2.0 (the "License");
  you may not use this file except in compliance with the License.
  You may obtain a copy of the License at

    http://www.apache.org/licenses/LICENSE-2.0

  Unless required by applicable law or agreed to in writing, software
  distributed under the License is distributed on an "AS IS" BASIS,
  WITHOUT WARRANTIES OR CONDITIONS OF ANY KIND, either express or
  implied.
  See the License for the specific language governing permissions and
  limitations under the License.
*/

module mgmt-interface {
    yang-version 1.1;
    namespace "urn:etsi:osm:yang:augments:mgmt-interface";
    prefix "mgmt-interface";

    import etsi-nfv-vnfd {
        prefix vnfd;
    }

    grouping extended-mgmt-interface {
        leaf mgmt-cp {
            description
              "Connection point over which the VNF is managed.";
            type leafref {
                path "/vnfd:vnfd/vnfd:ext-cpd/vnfd:id";
            }
        }
    }

    augment "/vnfd:vnfd" {
        uses extended-mgmt-interface;
    }
}
